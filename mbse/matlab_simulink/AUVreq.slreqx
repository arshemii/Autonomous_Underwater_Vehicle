# AUVreq
The system shall autonomously scan underwater pipelines

## MSN: Mission (Functional)
The system shall autonomously scan underwater pipelines

### STK-RQM: Stakeholder Requirements (Functional)
The system shall meet the requirements of stakeholders

#### MNT: Maintanance (Functional)
the system shall provide the technician with maintenance possibility

##### DIS: Disassembly (Functional)
The system shall use screw connections to provide disassembly option

##### RPLC: Replacement (Functional)
Inner components shall be accessible from the body interior for replacement

#### ENV: Environment (Functional)
The system shall be environmental friendly

##### CLR: Color (Functional)
The system shall use water proof colors

##### NS: Noise (Functional)
The system shall use low-noise motors

##### LKG: Leakage (Functional)
The system shall use a cover for the battery pack to avoid accidental leakages

### DT-CMN: Data Communication (Functional)
The system shall communicate with the landstation

#### TR: Send (Functional)
The system shall send data to the land station with 1 Hz frequency

##### PCKG: Data Packing (Functional)
The system shall prepare a packed log file of each pipeline section scan

##### ENC: Encryption (Functional)
The system shall encrypt diagnosis data before sending to the land station

#### RC: Receive (Functional)
The system shall receive the land station commands with a maximum 0.5 second delay

##### DEC: Decryption (Functional)
The system shall decrypt the mission message coming from the land station.

### LCL: Localization (Functional)
The system shall determine its global location

#### SDI: Sensor Data Integration (Functional)
The system shall perform data integration to find its pose configuration with less than 1m uncertainity

##### GNSS-SEP: NMEA Seperator (Functional)
The system shall obtain 3 positions' values from the NMEA message

###### GNSS: WGS84 Pose (Functional)
The system shall obtain its position in WGS84 coordinates with 1Hz

##### IMU-SEP: IMU Seperator (Functional)
The system shall separate IMU measurements based on their units

###### IMU: Angular Rate measurement (Functional)
The system shall obtain gyroscope data with 100Hz

### PLN: Motion Planning (Functional)
The system shall plan a trajectory for the mission coming from the landstation

#### Xi: Mission Xi (Functional)
The system shall receive the initial state of the mission

#### Xf: mission Xf (Functional)
The system shall receive the final state of the mission

### DGN: Diagnosis (Functional)
The system shall be able to find problems in the pipeline

#### OBJ-DET: Pipe Detection (Functional)
the system shall detect the presence of pipe in the camera frame

##### PG: photography (Functional)
the system shall start photography with 1 Hz when its distance with pipeline is less than 1 meter

#### SEM-SEG: Fault Detection (Functional)
The system shall perform fault detection on X-ray scans

##### RG: Radiography (Functional)
The system shall start radiography with 1 Hz when its distance with pipeline is less than 1 Hz

### CTRL: Motion Control (Functional)
The system shall move on the planned trajectory

#### R1: Motor 1 R (Functional)
The Motor 1 shall rotate in the planned RPM

##### C1: Motor C1 (Functional)
The system shall send the control input to motor 1

#### R2: Motor 2 R (Functional)
The Motor 2 shall rotate in the planned RPM

##### C2: Motor C2 (Functional)
The system shall send the control input to motor 2

#### R3: Motor 3 R (Functional)
The Motor 3 shall rotate in the planned RPM

##### C3: Motor C3 (Functional)
The system shall send the control input to motor 3

#### R4: Motor 4 R (Functional)
The Motor 4 shall rotate in the planned RPM

##### C4: Motor C4 (Functional)
The system shall send the control input to motor 4

### SFT: Safety (Functional)
The system shall have a safe mission

#### PR: Pressure Resistance (Functional)
The system shall resist pressure up to 1.5 Atm

#### WR: Water resistance (Functional)
The system shall be water proof for up to 10 hourse

#### SHP: Shark Pulse (Functional)
The system shall send pulses with a frequency of 0.1 Hz to keep large animals away

#### SNT: Salinity Resistance (Functional)
The system shall be protected against salinity

### RSRC: Resources (Functional)
The system shall store energy and data

#### CHRG: Battery Capacity (Functional)
The system shall store energy for up to 10 hours of operation

#### SOS: Emergency Mission End (Functional)
The system shall stop the mission when the battery SOC is less than 12%

##### #51: SOC Calculator (Functional)
The system shall determine the SOC of the battery

#### STRG-DTC: Pipe Detection Data (Functional)
The system shall be able to store Trained Pipe Detection Model

#### STRG-FLT: Fault Detection Data (Functional)
The system shall be able to store Trained Fault Detection Model
